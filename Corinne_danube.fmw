FME workspace Corinne_danube.fmw

Parameters:
- SourceDataset_POSTGIS = danube_2   # Connection
- SourceDataset_SHAPEFILE = $(FME_MF_DIR)GIS-data\corinne_danube.shp   # Source Esri Shapefile(s)
- DestDataset_SHAPEFILE = $(FME_MF_DIR)GIS-data   # Destination Esri Shapefile Folder
- SourceDataset_SHAPEFILE_3 = $(FME_MF_DIR)GIS-data\intersect_corinne_danube.shp   # Source Esri Shapefile(s)
- DestDataset_SHAPEFILE_2 = $(FME_MF_DIR)GIS-data   # Destination Esri Shapefile Folder

Readers:
- POSTGIS_1: POSTGIS from $(SourceDataset_POSTGIS)
- SHAPEFILE_1: SHAPEFILE from $(SourceDataset_SHAPEFILE) in EPSG:3035
- SHAPEFILE_2: SHAPEFILE from $(SourceDataset_SHAPEFILE_3) in EPSG:3035

Writers:
- SHAPEFILE_3: SHAPEFILE to $(DestDataset_SHAPEFILE) in EPSG:3035
- SHAPEFILE_4: SHAPEFILE to $(DestDataset_SHAPEFILE_2) in EPSG:3035

Bookmark: Landuse
corinne_danube (reader SHAPEFILE_1)
    attributes: OBJECTID number(20,0), code_00 char(3), ID char(18), Remark char(20), Area_Ha double, Shape_Leng double, Shape_Area double
    -> Clip_Landuse_inside_Buffer [CLIPPEE]

Bookmark: Wells
well_clusters (reader POSTGIS_1)
    attributes: id int8, jrccode varchar(26), code varchar(25), country varchar(8), location varchar(23), level1 varchar(128), level2 varchar(128), level3 varchar(128), level4 varchar(128), level5 varchar(128), xriv varchar(200), dow float8, elevation varchar(200), transmissi float8, hydr_condu float8, c_ind_man int4, c_ind_euc int4, id_ca varchar(200), note_ca varchar(200), hydr_con_ca varchar(200), x float8, y float8
    -> 3_km_Buffer
    -> FeatureJoiner_3 [LEFT]

Bookmark: Geoprocessing
3_km_Buffer: Bufferer
    ANGLE = 22.5
    CAP_STYLE = Round
    CORNER_STYLE = Round
    GROUP_BY = id
    MODE = AREA
    OFFSET = 3
    OFFSET_UNITS = KM
    BUFFERED -> AreaCalculator_2
AreaCalculator_2
    AREA_ATTR = buff_area
    AREA_TYPE = Plane Area
    MULT = 1
    -> AttributeRounder_2
AttributeRounder_2
    PLACES = 2
    ROUND_TYPE = Nearest
    SRC_ATTRS = buff_area
    -> Clip_Landuse_inside_Buffer [CLIPPER]
Clip_Landuse_inside_Buffer: Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> clipped_corinne (writer SHAPEFILE_3)

Bookmark: Landuse calculation in a 3km proximity of each well
Note: Due to hardware limitation this is not the "best practise-workflow", some processes has been divided into several transformations where one tranformator would do the trick.
clipped_corinne (writer SHAPEFILE_3)
    attributes: OBJECTID number(20,0), code_00 char(3), ID char(18), Remark char(20), Area_Ha double, Shape_Leng double, Shape_Area double, _clipped char(200)
complete_wellsv2 (writer SHAPEFILE_4)
    attributes: id number(20,0), jrccode char(26), code char(25), country char(8), location char(23), level1 char(128), level2 char(128), level3 char(128), level4 char(128), level5 char(128), xriv char(200), dow double, elevation char(200), transmissi double, hydr_condu double, c_ind_man long, c_ind_euc long, id_ca char(200), note_ca char(200), hydr_con_c char(200), x double, y double, id_2 number(20,0), Agricultur char(200), Coniferous char(200), Deciduous_ char(200), Urban char(200), Mixed_fore char(200), Scrubland_ char(200), Wetlands char(200),
      Water char(200)

Bookmark: Landuse inside bufferzone
intersect_corinne_danube (reader SHAPEFILE_2)
    attributes: OBJECTID number(20,0), code_00 char(3), ID char(18), Remark char(20), Area_Ha double, Shape_Leng double, Shape_Area double, _clipped char(200), id_2 number(20,0), jrccode char(26), code char(25), country char(8), location char(23), level1 char(128), level2 char(128), level3 char(128), level4 char(128), level5 char(128), xriv char(200), dow double, elevation char(200), transmissi double, hydr_condu double, c_ind_man long, c_ind_euc long, id_ca char(200), note_ca char(200), hydr_con_c char(200), x double, y double
    -> AttributeValueMapper

Bookmark: Attribute manipulation
AttributeValueMapper
    DIRECTION = Forward (Source To Destination)
    LUT = 111,Urban,112,Urban,121,Urban,122,Urban,123,Urban,124,Urban,131,Urban,132,Urban,133,Urban,141,Urban,142,Urban,211,Agriculture,221,Agriculture,222,Agriculture,231,Agriculture,242,Agriculture,243,Agriculture,311,Deciduous forest,312,Coniferous forest,313,Mixed forest,321,Scrubland/Open areas,322,Scrubland/Open areas,324,Scrubland/Open areas,331,Scrubland/Open areas,332,Scrubland/Open areas,333,Scrubland/Open areas,411,Wetlands,412,Wetlands,511,Water,512,Water
    SRC = code_00
    VAL_ATTR = Landuse
    -> AttributeManager
AttributeManager
    ATTR_TABLE:
      REMOVE OBJECTID
      REMOVE code_00
      REMOVE ID
      REMOVE Remark
      REMOVE Area_Ha
      REMOVE Shape_Leng
      REMOVE Shape_Area
      REMOVE _clipped
      SET_TO tot_area = 27553207.13
    -> AreaCalculator

Bookmark: Area and percentage calculation
AreaCalculator
    AREA_ATTR = Area
    AREA_TYPE = Plane Area
    MULT = 1
    -> AttributeRounder
AttributeRounder
    PLACES = 2
    ROUND_TYPE = Nearest
    SRC_ATTRS = Area
    -> ExpressionEvaluator
ExpressionEvaluator
    ACTION = Create New Attribute
    EXPRESSION = @Value(Area)/@Value(tot_area)*100
    VAL_ATTR = percentage
    -> AttributeRounder_3
AttributeRounder_3
    PLACES = 2
    ROUND_TYPE = Nearest
    SRC_ATTRS = percentage
    -> AttributeManager_2

Bookmark: Area percentage calculation and manipulation
Note: Area of specific landuse inside buffer / Total bufferarea
AttributeManager_2
    ATTR_TABLE:
      SET_TO Agriculture = FME_CONDITIONAL:DEFAULT_VALUE'_FME_NO_OP_'BOOL_OP;OR;COMPOSITE_TEST;1;TEST @Value(Landuse) = Agriculture'@Value(percentage)'FME_NUM_CONDITIONS2___
      SET_TO Urban = FME_CONDITIONAL:DEFAULT_VALUE'_FME_NO_OP_'BOOL_OP;OR;COMPOSITE_TEST;1;TEST @Value(Landuse) = Urban'@Value(percentage)'FME_NUM_CONDITIONS2___
      SET_TO Coniferous forest = FME_CONDITIONAL:DEFAULT_VALUE'_FME_NO_OP_'BOOL_OP;OR;COMPOSITE_TEST;1;TEST @Value(Landuse) = Coniferous forest'@Value(percentage)'FME_NUM_CONDITIONS2___
      SET_TO Mixed forest = FME_CONDITIONAL:DEFAULT_VALUE'_FME_NO_OP_'BOOL_OP;OR;COMPOSITE_TEST;1;TEST @Value(Landuse) = Mixed forest'@Value(percentage)'FME_NUM_CONDITIONS2___
      SET_TO Scrubland/Open areas = FME_CONDITIONAL:DEFAULT_VALUE'_FME_NO_OP_'BOOL_OP;OR;COMPOSITE_TEST;1;TEST @Value(Landuse) = Scrubland/Open areas'@Value(percentage)'FME_NUM_CONDITIONS2___
      SET_TO Wetlands = FME_CONDITIONAL:DEFAULT_VALUE'_FME_NO_OP_'BOOL_OP;OR;COMPOSITE_TEST;1;TEST @Value(Landuse) = Wetlands'@Value(percentage)'FME_NUM_CONDITIONS2___
      SET_TO Deciduous forest = FME_CONDITIONAL:DEFAULT_VALUE'_FME_NO_OP_'BOOL_OP;OR;COMPOSITE_TEST;1;TEST @Value(Landuse) = Deciduous forest'@Value(percentage)'FME_NUM_CONDITIONS2___
      SET_TO Water = FME_CONDITIONAL:DEFAULT_VALUE'_FME_NO_OP_'BOOL_OP;OR;COMPOSITE_TEST;1;TEST @Value(Landuse) = Water'@Value(percentage)'FME_NUM_CONDITIONS2___
    -> Aggregator_2
    -> Aggregator
    -> Aggregator_3

Bookmark: Sums complete Landuse area
Aggregator
    ACCUM_ATTRS_NAME = Drop Incoming Attributes
    GROUP_BY = id_2
    MODE = Attributes Only
    SEP = ,
    SUM = Agriculture
    AGGREGATE -> FeatureJoiner [LEFT]
Aggregator_2
    ACCUM_ATTRS_NAME = Drop Incoming Attributes
    GROUP_BY = id_2
    MODE = Attributes Only
    SEP = ,
    SUM = "Deciduous forest" "Coniferous forest"
    AGGREGATE -> FeatureJoiner [RIGHT]
Aggregator_3
    ACCUM_ATTRS_NAME = Drop Incoming Attributes
    GROUP_BY = id_2
    MODE = Attributes Only
    SEP = ,
    SUM = "Scrubland/Open areas" Water Wetlands "Mixed forest" Urban
    AGGREGATE -> FeatureJoiner_2 [RIGHT]

Bookmark: Join Landuse percentage with Wells
FeatureJoiner
    ATTR_CONFLICT_RES = Use Left
    GEOMETRY_HANDLING = Use Left
    JOIN_KEYS = id_2 id_2 AUTO
    JOIN_MODE = Inner
    JOINED -> FeatureJoiner_2 [LEFT]
FeatureJoiner_2
    ATTR_CONFLICT_RES = Use Left
    GEOMETRY_HANDLING = Use Left
    JOIN_KEYS = id_2 id_2 AUTO
    JOIN_MODE = Inner
    JOINED -> AttributeRounder_4
AttributeRounder_4
    PLACES = 2
    ROUND_TYPE = Nearest
    SRC_ATTRS = Deciduous forest Agriculture Urban Wetlands Mixed forest Water Scrubland/Open areas Coniferous forest
    -> FeatureJoiner_3 [RIGHT]
FeatureJoiner_3
    ATTR_CONFLICT_RES = Use Left
    GEOMETRY_HANDLING = Use Left
    JOIN_KEYS = id id_2 AUTO
    JOIN_MODE = Inner
    JOINED -> complete_wellsv2 (writer SHAPEFILE_4)
