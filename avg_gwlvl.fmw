FME workspace avg_gwlvl.fmw

Parameters:
- SourceDataset_CSV2 = C:\Users\Maestro\Documents\test12.csv   # Source CSV (Comma Separated Value) File(s)
- SourceDataset_SHAPEFILE = $(FME_MF_DIR)GIS-data\wells_windicies.shp   # Source Esri Shapefile(s)
- DestDataset_CSV2 = $(FME_MF_DIR)GIS-data   # Destination CSV (Comma Separated Value) Folder
- DestDataset_POSTGRES = danube_2   # Connection
- SourceDataset_XLSXR = $(FME_MF_DIR)GIS-data\mean_gw2.xlsx   # Source Microsoft Excel File(s)
- DestDataset_SHAPEFILE = $(FME_MF_DIR)GIS-data   # Destination Esri Shapefile Folder

Readers:
- CSV2_1: CSV2 from $(SourceDataset_CSV2)
- SHAPEFILE_1: SHAPEFILE from $(SourceDataset_SHAPEFILE)
- XLSXR_1: XLSXR from $(SourceDataset_XLSXR)

Writers:
- CSV2_2: CSV2 to $(DestDataset_CSV2)
- POSTGRES_1: POSTGRES to $(DestDataset_POSTGRES)
- SHAPEFILE_2: SHAPEFILE to $(DestDataset_SHAPEFILE) in EPSG:3035

CSV (reader CSV2_1)
    attributes: id string, date string, value string
    -> UniqueValueLogger
    -> TestFilter
TestFilter
    DEFAULT_VALUE = <UNFILTERED>
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30 OR 31 OR 32 OR 33 OR 34 OR 35 OR 36"""""",TEST_CLAUSE,TEST @Value(id) = 9932
      TEST @Value(id) = 11163
      TEST @Value(id) = 10362
      TEST @Value(id) = 9885
      TEST @Value(id) = 10272
      TEST @Value(id) = 9884
      TEST @Value(id) = 9883
      TEST @Value(id) = 9984
      TEST @Value(id) = 11039
      TEST @Value(id) = 10609
      TEST @Value(id) = 9872
      TEST @Value(id) = 9874
      TEST @Value(id) = 9877
      TEST @Value(id) = 9878
      TEST @Value(id) = 10961
      TEST @Value(id) = 9879
      TEST @Value(id) = 9953
      TEST @Value(id) = 11500
      TEST @Value(id) = 11158
      TEST @Value(id) = 9959
      TEST @Value(id) = 10998
      TEST @Value(id) = 10001
      TEST @Value(id) = 10255
      TEST @Value(id) = 9929
      TEST @Value(id) = 80331
      TEST @Value(id) = 10086
      TEST @Value(id) = 10660
      TEST @Value(id) = 10702
      TEST @Value(id) = 11685
      TEST @Value(id) = 11551
      TEST @Value(id) = 9994
      TEST @Value(id) = 11717
      TEST @Value(id) = 80887
      TEST @Value(id) = 80875
      TEST @Value(id) = 10000
      TEST @Value(id) = 9873",@Value(id) = 9932
    <UNFILTERED> -> StatisticsCalculator
    <UNFILTERED> -> value_series (writer POSTGRES_1)
value_series (writer POSTGRES_1)
    attributes: id text, date text, value text
StatisticsCalculator
    COMPUTE_HISTOGRAM = NO
    COUNT_ATTR = _count
    GROUP_BY = id
    MAX_ATTR = _max
    MEAN_ATTR = _mean
    MIN_ATTR = _min
    PREPEND_ATTR_NAME_CHOICE = For multiple results only
    STATS_ATTRS = value
    SUM_ATTR = _sum
    SUMMARY -> mean_gw (writer CSV2_2)
mean_gw (writer CSV2_2)
    attributes: id string, _min string, _max string, _count string, _sum string, _mean string
UniqueValueLogger
    VAL = @Value(id)
    -> FeatureJoiner [LEFT]
wells_windicies (reader SHAPEFILE_1)
    attributes: id number(16,0), jrccode char(26), code char(25), country char(8), location char(23), transmissi double, hydr_condu double, pid number(16,0), elevation char(200), LEVEL1 char(128), LEVEL2 char(128), LEVEL3 char(128), LEVEL4 char(128), LEVEL5 char(128), iaf,s char(254), iaf,y char(254), BLS char(254), l1 char(254), l2 char(254), l3 char(254), l4 char(254), bimod char(254), colwell,C char(254), colwell,M char(254), colwell,P char(254), cvmon,min char(254), cvmon,max char(254), dip char(254), dc,rng,01, char(254), dc,rng,02, char(254),
      dc,rng,025 char(254), med char(254), parde char(254), pulse,coun char(254), pulse,co00 char(254), pulse,dur, char(254), pulse,du00 char(254), pulse,cv,l char(254), pulse,cv,h char(254), bandwd char(254), vardoy,min char(254), vardoy,max char(254), freq char(254), trend char(254), seas char(254), autocor char(254), nonlinear char(254), skew char(254), kurt char(254), hurst char(254), lyapunov char(254), autocor,dc char(254), nonlinear, char(254), skew,dc char(254), kurt,dc char(254), id_ca char(200), note_ca char(200), hydr_con00 char(200), x double, y double,
      xriv char(200)
    -> FeatureJoiner [RIGHT]
    -> FeatureJoiner_2 [LEFT]
FeatureJoiner
    ATTR_CONFLICT_RES = Use Left
    GEOMETRY_HANDLING = Use Left
    JOIN_KEYS = _value id AUTO
    JOIN_MODE = Inner
Blad1 (reader XLSXR_1)
    attributes: wkt_geom char(60), id number(6,0), elevation number(10,5), id00 number(6,0), _mean number(17,13), dow number(20,16), G string, H string, I string, J string, K string, L string, M string, N string, O string, P string, Q string, R string, S string, T string, U string, V string, W string, X string, Y string, Z string, AA string, AB string, AC string, AD string,
      AE string, AF string, AG string, AH string, AI string, AJ string, AK string, AL string, AM string, AN string, AO string, AP string, AQ string, AR string, AS string, AT string
    -> FeatureJoiner_2 [RIGHT]
FeatureJoiner_2
    ATTR_CONFLICT_RES = Use Left
    GEOMETRY_HANDLING = Use Left
    JOIN_KEYS = id id AUTO
    JOIN_MODE = Inner
    JOINED -> AttributeManager
AttributeManager
    ATTR_TABLE:
      REMOVE wkt_geom
      REMOVE id00
      REMOVE G
      REMOVE H
      REMOVE I
      REMOVE J
      REMOVE K
      REMOVE L
      REMOVE M
      REMOVE N
      REMOVE O
      REMOVE P
      REMOVE Q
      REMOVE R
      REMOVE S
      REMOVE T
      REMOVE U
      REMOVE V
      REMOVE W
      REMOVE X
      REMOVE Y
      REMOVE Z
      REMOVE AA
      REMOVE AB
      REMOVE AC
      REMOVE AD
      REMOVE AE
      REMOVE AF
      REMOVE AG
      REMOVE AH
      REMOVE AI
      REMOVE AJ
      REMOVE AK
      REMOVE AL
      REMOVE AM
      REMOVE AN
      REMOVE AO
      REMOVE AP
      REMOVE AQ
      REMOVE AR
      REMOVE AS
      REMOVE AT
    -> wells_windicies (writer SHAPEFILE_2)
wells_windicies (writer SHAPEFILE_2)
    attributes: id number(16,0), jrccode char(26), code char(25), country char(8), location char(23), transmissi double, hydr_condu double, pid number(16,0), elevation char(200), LEVEL1 char(128), LEVEL2 char(128), LEVEL3 char(128), LEVEL4 char(128), LEVEL5 char(128), iaf,s char(254), iaf,y char(254), BLS char(254), l1 char(254), l2 char(254), l3 char(254), l4 char(254), bimod char(254), colwell,C char(254), colwell,M char(254), colwell,P char(254), cvmon,min char(254), cvmon,max char(254), dip char(254), dc,rng,01, char(254), dc,rng,02, char(254),
      dc,rng,025 char(254), med char(254), parde char(254), pulse,coun char(254), pulse,co00 char(254), pulse,dur, char(254), pulse,du00 char(254), pulse,cv,l char(254), pulse,cv,h char(254), bandwd char(254), vardoy,min char(254), vardoy,max char(254), freq char(254), trend char(254), seas char(254), autocor char(254), nonlinear char(254), skew char(254), kurt char(254), hurst char(254), lyapunov char(254), autocor,dc char(254), nonlinear, char(254), skew,dc char(254), kurt,dc char(254), id_ca char(200), note_ca char(200), hydr_con00 char(200), x double, y double,
      xriv char(200), _mean number(17,13), dow number(20,16)

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
